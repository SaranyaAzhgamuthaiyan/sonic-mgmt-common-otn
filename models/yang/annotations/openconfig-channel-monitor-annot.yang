module openconfig-channel-monitor-annot {

    yang-version "1";

    namespace "http://openconfig.net/yang/annotation/oc-chan-monitor-annot";
    prefix "oc-chan-monitor-annot";

    import sonic-extensions { prefix sonic-ext; }
    import openconfig-extensions { prefix oc-ext; }
    import openconfig-interfaces { prefix oc-if; }
    import openconfig-platform { prefix oc-platform; }
    import openconfig-transport-types { prefix oc-opt-types; }
    import openconfig-channel-monitor { prefix oc-chan-monitor; }

    deviation /oc-chan-monitor:channel-monitors {
      deviate add {
       sonic-ext:get-namespace "ocm_get_namespace_xfmr";
      }
    }

    deviation /oc-chan-monitor:channel-monitors/oc-chan-monitor:channel-monitor {
      deviate add {
        sonic-ext:table-name "OTN_OCM";
        sonic-ext:key-transformer "ocm_name_key_xfmr";
      }
    }

    deviation /oc-chan-monitor:channel-monitors/oc-chan-monitor:channel-monitor/oc-chan-monitor:channels {
      deviate add {
        sonic-ext:db-name "STATE_DB";
      }
    }

    deviation /oc-chan-monitor:channel-monitors/oc-chan-monitor:channel-monitor/oc-chan-monitor:channels/oc-chan-monitor:channel {
      deviate add {
        sonic-ext:table-name "OTN_OCM_CHANNEL_TABLE"; 
        sonic-ext:key-transformer "ocm_channel_key_xfmr";
      }
    }

    deviation /oc-chan-monitor:channel-monitors/oc-chan-monitor:channel-monitor/oc-chan-monitor:channels/oc-chan-monitor:channel/oc-chan-monitor:state {
      deviate add {
        sonic-ext:db-name "STATE_DB";
        sonic-ext:table-name "OTN_OCM_CHANNEL_TABLE";
        sonic-ext:key-transformer "ocm_channel_key_xfmr";
      }
    }

    deviation /oc-chan-monitor:channel-monitors/oc-chan-monitor:channel-monitor/oc-chan-monitor:channels/oc-chan-monitor:channel/oc-chan-monitor:state/oc-chan-monitor:lower-frequency {
      deviate add {
        sonic-ext:field-transformer "ocm_lower_frequency_field_xfmr";
      }
    }

    deviation /oc-chan-monitor:channel-monitors/oc-chan-monitor:channel-monitor/oc-chan-monitor:channels/oc-chan-monitor:channel/oc-chan-monitor:state/oc-chan-monitor:upper-frequency {
      deviate add {
        sonic-ext:field-transformer "ocm_upper_frequency_field_xfmr";
      }
    }

    deviation /oc-chan-monitor:channel-monitors/oc-chan-monitor:channel-monitor/oc-chan-monitor:channels/oc-chan-monitor:channel/oc-chan-monitor:state/oc-chan-monitor:power {
      deviate add {
        sonic-ext:field-name "power";
      }
    }

    deviation /oc-chan-monitor:channel-monitors/oc-chan-monitor:channel-monitor/oc-chan-monitor:channels/oc-chan-monitor:channel/oc-chan-monitor:state/oc-chan-monitor:target-power {
      deviate add {
        sonic-ext:field-name "target-power";
      }
    }

    deviation /oc-chan-monitor:channel-monitors/oc-chan-monitor:channel-monitor/oc-chan-monitor:channels/oc-chan-monitor:channel/oc-chan-monitor:lower-frequency {
      deviate add {
      }
    }

    deviation /oc-chan-monitor:channel-monitors/oc-chan-monitor:channel-monitor/oc-chan-monitor:channels/oc-chan-monitor:channel/oc-chan-monitor:upper-frequency {
      deviate add {
      }
    }

    deviation /oc-chan-monitor:channel-monitors/oc-chan-monitor:channel-monitor/oc-chan-monitor:name {
      deviate add {
      }
    }

    deviation /oc-chan-monitor:channel-monitors/oc-chan-monitor:channel-monitor/oc-chan-monitor:config {
      deviate add {
      }
    }

    deviation /oc-chan-monitor:channel-monitors/oc-chan-monitor:channel-monitor/oc-chan-monitor:config/oc-chan-monitor:name {
      deviate add {
      }
    }

    deviation /oc-chan-monitor:channel-monitors/oc-chan-monitor:channel-monitor/oc-chan-monitor:config/oc-chan-monitor:monitor-port {
      deviate add {
        sonic-ext:field-name "monitor-port";
      }
    }

    deviation /oc-chan-monitor:channel-monitors/oc-chan-monitor:channel-monitor/oc-chan-monitor:state {
      deviate add {
        sonic-ext:db-name "STATE_DB";
        sonic-ext:table-name "OTN_OCM_TABLE";
        sonic-ext:key-transformer "ocm_name_key_xfmr";
      }
    }

    deviation /oc-chan-monitor:channel-monitors/oc-chan-monitor:channel-monitor/oc-chan-monitor:state/oc-chan-monitor:monitor-port {
      deviate add {
        sonic-ext:field-name "monitor-port";
      }
    }

    deviation /oc-chan-monitor:channel-monitors/oc-chan-monitor:channel-monitor/oc-chan-monitor:state/oc-chan-monitor:name {
      deviate add {
      }
    }

}
